// SPDX-FileCopyrightText: 2026 CERN
// SPDX-FileCopyrightText: 2026 Kari Vierimaa, Kempele, Finland
// SPDX-License-Identifier: CERN-OHL-W-2.0
//
// Structural model. Edit this file before the matching SystemVerilog module.
// Baseline extracted from src/ on 2026-09-27.
// Upstream: https://gitlab.com/colibri-cern/colibri commit 3fa784121ccea86d9e65b2e0dc08d2a3327f5f2f

package Colibri_Misc_be_remove_lead {
    private import ScalarValues::*;
    private import ArchitectureMeta::*;
    private import Colibri_Requirements::*;

    @ArtifactTrace {
        rtlPath = "src/misc/be_remove_lead.sv";
        verifPath = "sim/misc/be_remove_lead_tb.sv";
        fvPath = "fv/misc/be_remove_lead_sva.sv";
    }
    part def be_remove_lead {
        doc /* Structural contract for the SystemVerilog module. RTL follows this part. */
        attribute g_DATA_WIDTH : Integer = 32;
        attribute g_REGISTER_OUT : Boolean = false;

        in item clk_i;
        in item reset_i;
        in item shl_i;
        attribute shl_i_sv : String = "logic [colibri_utils::log2ceil(int'(g_DATA_WIDTH) / 8):0] shl_i";
        out item snk_ready_o;
        in item snk_valid_i;
        in item snk_sop_i;
        in item snk_eop_i;
        in item snk_empty_i;
        attribute snk_empty_i_sv : String = "logic [colibri_utils::downto_width(colibri_utils::log2ceil(int'(g_DATA_WIDTH) / 8))-1:0] snk_empty_i";
        in item snk_data_i;
        attribute snk_data_i_sv : String = "logic [g_DATA_WIDTH-1:0] snk_data_i";
        in item src_ready_i;
        out item src_valid_o;
        out item src_sop_o;
        out item src_eop_o;
        out item src_empty_o;
        attribute src_empty_o_sv : String = "logic [colibri_utils::downto_width(colibri_utils::log2ceil(int'(g_DATA_WIDTH) / 8))-1:0] src_empty_o";
        out item src_data_o;
        attribute src_data_o_sv : String = "logic [g_DATA_WIDTH-1:0] src_data_o";
        out item src_head_o;
        attribute src_head_o_sv : String = "logic [g_DATA_WIDTH-1:0] src_head_o";
        satisfy requirement REQ_BE_REMOVE_LEAD_001;
        satisfy requirement REQ_BE_REMOVE_LEAD_002;
        satisfy requirement REQ_BE_REMOVE_LEAD_003;

    }

    part beRemoveLeadUse : be_remove_lead;
}
