// SPDX-FileCopyrightText: 2026 CERN
// SPDX-FileCopyrightText: 2026 Kari Vierimaa, Kempele, Finland
// SPDX-License-Identifier: CERN-OHL-W-2.0
//
// Structural model. Edit this file before the matching SystemVerilog module.
// Baseline extracted from src/ on 2026-09-27.
// Upstream: https://gitlab.com/colibri-cern/colibri commit 3fa784121ccea86d9e65b2e0dc08d2a3327f5f2f

package Colibri_Comms_gearbox {
    private import ScalarValues::*;
    private import ArchitectureMeta::*;
    private import Colibri_Requirements::*;

    @ArtifactTrace {
        rtlPath = "src/comms/gearbox.sv";
    }
    part def gearbox {
        doc /* Structural contract for the SystemVerilog module. RTL follows this part. */
        attribute g_INPUT_WIDTH : Integer = 8;
        attribute g_OUTPUT_WIDTH : Integer = 8;

        in item clk_i;
        in item reset_i;
        in item snk_data_i;
        attribute snk_data_i_sv : String = "logic [g_INPUT_WIDTH-1:0] snk_data_i";
        in item snk_valid_i;
        out item snk_ready_o;
        out item src_data_o;
        attribute src_data_o_sv : String = "logic [g_OUTPUT_WIDTH-1:0] src_data_o";
        out item src_valid_o;
        in item src_ready_i;
        satisfy requirement REQ_GEARBOX_001;
        satisfy requirement REQ_GEARBOX_002;
        satisfy requirement REQ_GEARBOX_003;
        satisfy requirement REQ_GEARBOX_004;
        satisfy requirement REQ_GEARBOX_005;
        satisfy requirement REQ_GEARBOX_006;

    }

    part gearboxUse : gearbox;
}
