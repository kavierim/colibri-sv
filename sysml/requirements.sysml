// SPDX-FileCopyrightText: 2026 Kari Vierimaa, Kempele, Finland
//
// Ancillary repository file (not Covered Source). RTL is under CERN-OHL-W; see NOTICE.

package Colibri_Requirements {
    doc /*
     * Requirement stubs. SHALL prose lives only in docs/modules.
     * Add a stub when a module page gains a REQ-* heading.
     */

    private import ScalarValues::*;
    private import ArchitectureMeta::*;

    @OKFReference {
        docPath = "docs/modules/common/counter.md";
        conceptId = "modules/common/counter";
        section = "REQ-COUNTER-001";
    }
    requirement def <'REQ-COUNTER-001'> REQ_COUNTER_001 {
        doc /* OKF: docs/modules/common/counter.md#REQ-COUNTER-001 */
        require constraint { true == true }
    }

    @OKFReference {
        docPath = "docs/modules/common/counter.md";
        conceptId = "modules/common/counter";
        section = "REQ-COUNTER-002";
    }
    requirement def <'REQ-COUNTER-002'> REQ_COUNTER_002 {
        doc /* OKF: docs/modules/common/counter.md#REQ-COUNTER-002 */
        require constraint { true == true }
    }

    @OKFReference {
        docPath = "docs/modules/common/counter.md";
        conceptId = "modules/common/counter";
        section = "REQ-COUNTER-003";
    }
    requirement def <'REQ-COUNTER-003'> REQ_COUNTER_003 {
        doc /* OKF: docs/modules/common/counter.md#REQ-COUNTER-003 */
        require constraint { true == true }
    }

    @OKFReference {
        docPath = "docs/modules/common/counter.md";
        conceptId = "modules/common/counter";
        section = "REQ-COUNTER-004";
    }
    requirement def <'REQ-COUNTER-004'> REQ_COUNTER_004 {
        doc /* OKF: docs/modules/common/counter.md#REQ-COUNTER-004 */
        require constraint { true == true }
    }

    @OKFReference {
        docPath = "docs/modules/common/debouncer.md";
        conceptId = "modules/common/debouncer";
        section = "REQ-DEBOUNCER-001";
    }
    requirement def <'REQ-DEBOUNCER-001'> REQ_DEBOUNCER_001 {
        doc /* OKF: docs/modules/common/debouncer.md#REQ-DEBOUNCER-001 */
        require constraint { true == true }
    }

    @OKFReference {
        docPath = "docs/modules/common/debouncer.md";
        conceptId = "modules/common/debouncer";
        section = "REQ-DEBOUNCER-002";
    }
    requirement def <'REQ-DEBOUNCER-002'> REQ_DEBOUNCER_002 {
        doc /* OKF: docs/modules/common/debouncer.md#REQ-DEBOUNCER-002 */
        require constraint { true == true }
    }

    @OKFReference {
        docPath = "docs/modules/common/debouncer.md";
        conceptId = "modules/common/debouncer";
        section = "REQ-DEBOUNCER-003";
    }
    requirement def <'REQ-DEBOUNCER-003'> REQ_DEBOUNCER_003 {
        doc /* OKF: docs/modules/common/debouncer.md#REQ-DEBOUNCER-003 */
        require constraint { true == true }
    }

    @OKFReference {
        docPath = "docs/modules/common/skid_buffer.md";
        conceptId = "modules/common/skid_buffer";
        section = "REQ-SKID_BUFFER-001";
    }
    requirement def <'REQ-SKID_BUFFER-001'> REQ_SKID_BUFFER_001 {
        doc /* OKF: docs/modules/common/skid_buffer.md#REQ-SKID_BUFFER-001 */
        require constraint { true == true }
    }

    @OKFReference {
        docPath = "docs/modules/common/skid_buffer.md";
        conceptId = "modules/common/skid_buffer";
        section = "REQ-SKID_BUFFER-002";
    }
    requirement def <'REQ-SKID_BUFFER-002'> REQ_SKID_BUFFER_002 {
        doc /* OKF: docs/modules/common/skid_buffer.md#REQ-SKID_BUFFER-002 */
        require constraint { true == true }
    }

    @OKFReference {
        docPath = "docs/modules/common/skid_buffer.md";
        conceptId = "modules/common/skid_buffer";
        section = "REQ-SKID_BUFFER-003";
    }
    requirement def <'REQ-SKID_BUFFER-003'> REQ_SKID_BUFFER_003 {
        doc /* OKF: docs/modules/common/skid_buffer.md#REQ-SKID_BUFFER-003 */
        require constraint { true == true }
    }

    @OKFReference {
        docPath = "docs/modules/common/skid_buffer.md";
        conceptId = "modules/common/skid_buffer";
        section = "REQ-SKID_BUFFER-004";
    }
    requirement def <'REQ-SKID_BUFFER-004'> REQ_SKID_BUFFER_004 {
        doc /* OKF: docs/modules/common/skid_buffer.md#REQ-SKID_BUFFER-004 */
        require constraint { true == true }
    }

    @OKFReference {
        docPath = "docs/modules/common/skid_buffer.md";
        conceptId = "modules/common/skid_buffer";
        section = "REQ-SKID_BUFFER-005";
    }
    requirement def <'REQ-SKID_BUFFER-005'> REQ_SKID_BUFFER_005 {
        doc /* OKF: docs/modules/common/skid_buffer.md#REQ-SKID_BUFFER-005 */
        require constraint { true == true }
    }

    @OKFReference {
        docPath = "docs/modules/common/pipeline_buffer.md";
        conceptId = "modules/common/pipeline_buffer";
        section = "REQ-PIPELINE_BUFFER-001";
    }
    requirement def <'REQ-PIPELINE_BUFFER-001'> REQ_PIPELINE_BUFFER_001 {
        doc /* OKF: docs/modules/common/pipeline_buffer.md#REQ-PIPELINE_BUFFER-001 */
        require constraint { true == true }
    }

    @OKFReference {
        docPath = "docs/modules/common/pipeline_buffer.md";
        conceptId = "modules/common/pipeline_buffer";
        section = "REQ-PIPELINE_BUFFER-002";
    }
    requirement def <'REQ-PIPELINE_BUFFER-002'> REQ_PIPELINE_BUFFER_002 {
        doc /* OKF: docs/modules/common/pipeline_buffer.md#REQ-PIPELINE_BUFFER-002 */
        require constraint { true == true }
    }

    @OKFReference {
        docPath = "docs/modules/common/pipeline_buffer.md";
        conceptId = "modules/common/pipeline_buffer";
        section = "REQ-PIPELINE_BUFFER-003";
    }
    requirement def <'REQ-PIPELINE_BUFFER-003'> REQ_PIPELINE_BUFFER_003 {
        doc /* OKF: docs/modules/common/pipeline_buffer.md#REQ-PIPELINE_BUFFER-003 */
        require constraint { true == true }
    }

    @OKFReference {
        docPath = "docs/modules/common/pipeline_buffer.md";
        conceptId = "modules/common/pipeline_buffer";
        section = "REQ-PIPELINE_BUFFER-004";
    }
    requirement def <'REQ-PIPELINE_BUFFER-004'> REQ_PIPELINE_BUFFER_004 {
        doc /* OKF: docs/modules/common/pipeline_buffer.md#REQ-PIPELINE_BUFFER-004 */
        require constraint { true == true }
    }

    @OKFReference {
        docPath = "docs/modules/common/pipeline_buffer.md";
        conceptId = "modules/common/pipeline_buffer";
        section = "REQ-PIPELINE_BUFFER-005";
    }
    requirement def <'REQ-PIPELINE_BUFFER-005'> REQ_PIPELINE_BUFFER_005 {
        doc /* OKF: docs/modules/common/pipeline_buffer.md#REQ-PIPELINE_BUFFER-005 */
        require constraint { true == true }
    }

    @OKFReference {
        docPath = "docs/modules/common/pipeline_buffer.md";
        conceptId = "modules/common/pipeline_buffer";
        section = "REQ-PIPELINE_BUFFER-006";
    }
    requirement def <'REQ-PIPELINE_BUFFER-006'> REQ_PIPELINE_BUFFER_006 {
        doc /* OKF: docs/modules/common/pipeline_buffer.md#REQ-PIPELINE_BUFFER-006 */
        require constraint { true == true }
    }

    @OKFReference {
        docPath = "docs/modules/common/stream_buffer.md";
        conceptId = "modules/common/stream_buffer";
        section = "REQ-STREAM_BUFFER-001";
    }
    requirement def <'REQ-STREAM_BUFFER-001'> REQ_STREAM_BUFFER_001 {
        doc /* OKF: docs/modules/common/stream_buffer.md#REQ-STREAM_BUFFER-001 */
        require constraint { true == true }
    }

    @OKFReference {
        docPath = "docs/modules/common/stream_buffer.md";
        conceptId = "modules/common/stream_buffer";
        section = "REQ-STREAM_BUFFER-002";
    }
    requirement def <'REQ-STREAM_BUFFER-002'> REQ_STREAM_BUFFER_002 {
        doc /* OKF: docs/modules/common/stream_buffer.md#REQ-STREAM_BUFFER-002 */
        require constraint { true == true }
    }

    @OKFReference {
        docPath = "docs/modules/common/stream_buffer.md";
        conceptId = "modules/common/stream_buffer";
        section = "REQ-STREAM_BUFFER-003";
    }
    requirement def <'REQ-STREAM_BUFFER-003'> REQ_STREAM_BUFFER_003 {
        doc /* OKF: docs/modules/common/stream_buffer.md#REQ-STREAM_BUFFER-003 */
        require constraint { true == true }
    }

    @OKFReference {
        docPath = "docs/modules/common/edge_detect.md";
        conceptId = "modules/common/edge_detect";
        section = "REQ-EDGE_DETECT-001";
    }
    requirement def <'REQ-EDGE_DETECT-001'> REQ_EDGE_DETECT_001 {
        doc /* OKF: docs/modules/common/edge_detect.md#REQ-EDGE_DETECT-001 */
        require constraint { true == true }
    }

    @OKFReference {
        docPath = "docs/modules/common/edge_detect.md";
        conceptId = "modules/common/edge_detect";
        section = "REQ-EDGE_DETECT-002";
    }
    requirement def <'REQ-EDGE_DETECT-002'> REQ_EDGE_DETECT_002 {
        doc /* OKF: docs/modules/common/edge_detect.md#REQ-EDGE_DETECT-002 */
        require constraint { true == true }
    }

    @OKFReference {
        docPath = "docs/modules/common/edge_detect.md";
        conceptId = "modules/common/edge_detect";
        section = "REQ-EDGE_DETECT-003";
    }
    requirement def <'REQ-EDGE_DETECT-003'> REQ_EDGE_DETECT_003 {
        doc /* OKF: docs/modules/common/edge_detect.md#REQ-EDGE_DETECT-003 */
        require constraint { true == true }
    }

    @OKFReference {
        docPath = "docs/modules/pipes/arbiter.md";
        conceptId = "modules/pipes/arbiter";
        section = "REQ-ARBITER-001";
    }
    requirement def <'REQ-ARBITER-001'> REQ_ARBITER_001 {
        doc /* OKF: docs/modules/pipes/arbiter.md#REQ-ARBITER-001 */
        require constraint { true == true }
    }

    @OKFReference {
        docPath = "docs/modules/pipes/arbiter.md";
        conceptId = "modules/pipes/arbiter";
        section = "REQ-ARBITER-002";
    }
    requirement def <'REQ-ARBITER-002'> REQ_ARBITER_002 {
        doc /* OKF: docs/modules/pipes/arbiter.md#REQ-ARBITER-002 */
        require constraint { true == true }
    }

    @OKFReference {
        docPath = "docs/modules/pipes/arbiter.md";
        conceptId = "modules/pipes/arbiter";
        section = "REQ-ARBITER-003";
    }
    requirement def <'REQ-ARBITER-003'> REQ_ARBITER_003 {
        doc /* OKF: docs/modules/pipes/arbiter.md#REQ-ARBITER-003 */
        require constraint { true == true }
    }

    @OKFReference {
        docPath = "docs/modules/pipes/arbiter.md";
        conceptId = "modules/pipes/arbiter";
        section = "REQ-ARBITER-004";
    }
    requirement def <'REQ-ARBITER-004'> REQ_ARBITER_004 {
        doc /* OKF: docs/modules/pipes/arbiter.md#REQ-ARBITER-004 */
        require constraint { true == true }
    }

    @OKFReference {
        docPath = "docs/modules/pipes/arbiter.md";
        conceptId = "modules/pipes/arbiter";
        section = "REQ-ARBITER-005";
    }
    requirement def <'REQ-ARBITER-005'> REQ_ARBITER_005 {
        doc /* OKF: docs/modules/pipes/arbiter.md#REQ-ARBITER-005 */
        require constraint { true == true }
    }

    @OKFReference {
        docPath = "docs/modules/pipes/arbiter.md";
        conceptId = "modules/pipes/arbiter";
        section = "REQ-ARBITER-006";
    }
    requirement def <'REQ-ARBITER-006'> REQ_ARBITER_006 {
        doc /* OKF: docs/modules/pipes/arbiter.md#REQ-ARBITER-006 */
        require constraint { true == true }
    }

    @OKFReference {
        docPath = "docs/modules/memory/fifo.md";
        conceptId = "modules/memory/fifo";
        section = "REQ-FIFO-001";
    }
    requirement def <'REQ-FIFO-001'> REQ_FIFO_001 {
        doc /* OKF: docs/modules/memory/fifo.md#REQ-FIFO-001 */
        require constraint { true == true }
    }

    @OKFReference {
        docPath = "docs/modules/memory/fifo.md";
        conceptId = "modules/memory/fifo";
        section = "REQ-FIFO-002";
    }
    requirement def <'REQ-FIFO-002'> REQ_FIFO_002 {
        doc /* OKF: docs/modules/memory/fifo.md#REQ-FIFO-002 */
        require constraint { true == true }
    }

    @OKFReference {
        docPath = "docs/modules/memory/fifo.md";
        conceptId = "modules/memory/fifo";
        section = "REQ-FIFO-003";
    }
    requirement def <'REQ-FIFO-003'> REQ_FIFO_003 {
        doc /* OKF: docs/modules/memory/fifo.md#REQ-FIFO-003 */
        require constraint { true == true }
    }

    @OKFReference {
        docPath = "docs/modules/memory/fifo.md";
        conceptId = "modules/memory/fifo";
        section = "REQ-FIFO-004";
    }
    requirement def <'REQ-FIFO-004'> REQ_FIFO_004 {
        doc /* OKF: docs/modules/memory/fifo.md#REQ-FIFO-004 */
        require constraint { true == true }
    }

    @OKFReference {
        docPath = "docs/modules/memory/fifo.md";
        conceptId = "modules/memory/fifo";
        section = "REQ-FIFO-005";
    }
    requirement def <'REQ-FIFO-005'> REQ_FIFO_005 {
        doc /* OKF: docs/modules/memory/fifo.md#REQ-FIFO-005 */
        require constraint { true == true }
    }

    @OKFReference {
        docPath = "docs/modules/memory/fifo.md";
        conceptId = "modules/memory/fifo";
        section = "REQ-FIFO-006";
    }
    requirement def <'REQ-FIFO-006'> REQ_FIFO_006 {
        doc /* OKF: docs/modules/memory/fifo.md#REQ-FIFO-006 */
        require constraint { true == true }
    }

    @OKFReference {
        docPath = "docs/modules/memory/fifo.md";
        conceptId = "modules/memory/fifo";
        section = "REQ-FIFO-007";
    }
    requirement def <'REQ-FIFO-007'> REQ_FIFO_007 {
        doc /* OKF: docs/modules/memory/fifo.md#REQ-FIFO-007 */
        require constraint { true == true }
    }

    @OKFReference {
        docPath = "docs/modules/memory/fifo.md";
        conceptId = "modules/memory/fifo";
        section = "REQ-FIFO-008";
    }
    requirement def <'REQ-FIFO-008'> REQ_FIFO_008 {
        doc /* OKF: docs/modules/memory/fifo.md#REQ-FIFO-008 */
        require constraint { true == true }
    }

    @OKFReference {
        docPath = "docs/modules/memory/fifo.md";
        conceptId = "modules/memory/fifo";
        section = "REQ-FIFO-009";
    }
    requirement def <'REQ-FIFO-009'> REQ_FIFO_009 {
        doc /* OKF: docs/modules/memory/fifo.md#REQ-FIFO-009 */
        require constraint { true == true }
    }

    @OKFReference {
        docPath = "docs/modules/memory/fifo.md";
        conceptId = "modules/memory/fifo";
        section = "REQ-FIFO-010";
    }
    requirement def <'REQ-FIFO-010'> REQ_FIFO_010 {
        doc /* OKF: docs/modules/memory/fifo.md#REQ-FIFO-010 */
        require constraint { true == true }
    }

    @OKFReference {
        docPath = "docs/modules/memory/ring_buffer.md";
        conceptId = "modules/memory/ring_buffer";
        section = "REQ-RING_BUFFER-001";
    }
    requirement def <'REQ-RING_BUFFER-001'> REQ_RING_BUFFER_001 {
        doc /* OKF: docs/modules/memory/ring_buffer.md#REQ-RING_BUFFER-001 */
        require constraint { true == true }
    }

    @OKFReference {
        docPath = "docs/modules/memory/ring_buffer.md";
        conceptId = "modules/memory/ring_buffer";
        section = "REQ-RING_BUFFER-002";
    }
    requirement def <'REQ-RING_BUFFER-002'> REQ_RING_BUFFER_002 {
        doc /* OKF: docs/modules/memory/ring_buffer.md#REQ-RING_BUFFER-002 */
        require constraint { true == true }
    }

    @OKFReference {
        docPath = "docs/modules/memory/ring_buffer.md";
        conceptId = "modules/memory/ring_buffer";
        section = "REQ-RING_BUFFER-003";
    }
    requirement def <'REQ-RING_BUFFER-003'> REQ_RING_BUFFER_003 {
        doc /* OKF: docs/modules/memory/ring_buffer.md#REQ-RING_BUFFER-003 */
        require constraint { true == true }
    }

    @OKFReference {
        docPath = "docs/modules/memory/ring_buffer.md";
        conceptId = "modules/memory/ring_buffer";
        section = "REQ-RING_BUFFER-004";
    }
    requirement def <'REQ-RING_BUFFER-004'> REQ_RING_BUFFER_004 {
        doc /* OKF: docs/modules/memory/ring_buffer.md#REQ-RING_BUFFER-004 */
        require constraint { true == true }
    }

    @OKFReference {
        docPath = "docs/modules/memory/ring_buffer.md";
        conceptId = "modules/memory/ring_buffer";
        section = "REQ-RING_BUFFER-005";
    }
    requirement def <'REQ-RING_BUFFER-005'> REQ_RING_BUFFER_005 {
        doc /* OKF: docs/modules/memory/ring_buffer.md#REQ-RING_BUFFER-005 */
        require constraint { true == true }
    }

    @OKFReference {
        docPath = "docs/modules/memory/ring_buffer.md";
        conceptId = "modules/memory/ring_buffer";
        section = "REQ-RING_BUFFER-006";
    }
    requirement def <'REQ-RING_BUFFER-006'> REQ_RING_BUFFER_006 {
        doc /* OKF: docs/modules/memory/ring_buffer.md#REQ-RING_BUFFER-006 */
        require constraint { true == true }
    }

    @OKFReference {
        docPath = "docs/modules/packet/header_add.md";
        conceptId = "modules/packet/header_add";
        section = "REQ-HEADER_ADD-001";
    }
    requirement def <'REQ-HEADER_ADD-001'> REQ_HEADER_ADD_001 {
        doc /* OKF: docs/modules/packet/header_add.md#REQ-HEADER_ADD-001 */
        require constraint { true == true }
    }

    @OKFReference {
        docPath = "docs/modules/packet/header_add.md";
        conceptId = "modules/packet/header_add";
        section = "REQ-HEADER_ADD-002";
    }
    requirement def <'REQ-HEADER_ADD-002'> REQ_HEADER_ADD_002 {
        doc /* OKF: docs/modules/packet/header_add.md#REQ-HEADER_ADD-002 */
        require constraint { true == true }
    }

    @OKFReference {
        docPath = "docs/modules/packet/header_add.md";
        conceptId = "modules/packet/header_add";
        section = "REQ-HEADER_ADD-003";
    }
    requirement def <'REQ-HEADER_ADD-003'> REQ_HEADER_ADD_003 {
        doc /* OKF: docs/modules/packet/header_add.md#REQ-HEADER_ADD-003 */
        require constraint { true == true }
    }

    @OKFReference {
        docPath = "docs/modules/packet/header_remove.md";
        conceptId = "modules/packet/header_remove";
        section = "REQ-HEADER_REMOVE-001";
    }
    requirement def <'REQ-HEADER_REMOVE-001'> REQ_HEADER_REMOVE_001 {
        doc /* OKF: docs/modules/packet/header_remove.md#REQ-HEADER_REMOVE-001 */
        require constraint { true == true }
    }

    @OKFReference {
        docPath = "docs/modules/packet/header_remove.md";
        conceptId = "modules/packet/header_remove";
        section = "REQ-HEADER_REMOVE-002";
    }
    requirement def <'REQ-HEADER_REMOVE-002'> REQ_HEADER_REMOVE_002 {
        doc /* OKF: docs/modules/packet/header_remove.md#REQ-HEADER_REMOVE-002 */
        require constraint { true == true }
    }

    @OKFReference {
        docPath = "docs/modules/packet/header_remove.md";
        conceptId = "modules/packet/header_remove";
        section = "REQ-HEADER_REMOVE-003";
    }
    requirement def <'REQ-HEADER_REMOVE-003'> REQ_HEADER_REMOVE_003 {
        doc /* OKF: docs/modules/packet/header_remove.md#REQ-HEADER_REMOVE-003 */
        require constraint { true == true }
    }

    @OKFReference {
        docPath = "docs/modules/packet/broadcaster.md";
        conceptId = "modules/packet/broadcaster";
        section = "REQ-BROADCASTER-001";
    }
    requirement def <'REQ-BROADCASTER-001'> REQ_BROADCASTER_001 {
        doc /* OKF: docs/modules/packet/broadcaster.md#REQ-BROADCASTER-001 */
        require constraint { true == true }
    }

    @OKFReference {
        docPath = "docs/modules/packet/broadcaster.md";
        conceptId = "modules/packet/broadcaster";
        section = "REQ-BROADCASTER-002";
    }
    requirement def <'REQ-BROADCASTER-002'> REQ_BROADCASTER_002 {
        doc /* OKF: docs/modules/packet/broadcaster.md#REQ-BROADCASTER-002 */
        require constraint { true == true }
    }

    @OKFReference {
        docPath = "docs/modules/packet/deinterleaver.md";
        conceptId = "modules/packet/deinterleaver";
        section = "REQ-DEINTERLEAVER-001";
    }
    requirement def <'REQ-DEINTERLEAVER-001'> REQ_DEINTERLEAVER_001 {
        doc /* OKF: docs/modules/packet/deinterleaver.md#REQ-DEINTERLEAVER-001 */
        require constraint { true == true }
    }

    @OKFReference {
        docPath = "docs/modules/packet/deinterleaver.md";
        conceptId = "modules/packet/deinterleaver";
        section = "REQ-DEINTERLEAVER-002";
    }
    requirement def <'REQ-DEINTERLEAVER-002'> REQ_DEINTERLEAVER_002 {
        doc /* OKF: docs/modules/packet/deinterleaver.md#REQ-DEINTERLEAVER-002 */
        require constraint { true == true }
    }

    @OKFReference {
        docPath = "docs/modules/packet/deinterleaver.md";
        conceptId = "modules/packet/deinterleaver";
        section = "REQ-DEINTERLEAVER-003";
    }
    requirement def <'REQ-DEINTERLEAVER-003'> REQ_DEINTERLEAVER_003 {
        doc /* OKF: docs/modules/packet/deinterleaver.md#REQ-DEINTERLEAVER-003 */
        require constraint { true == true }
    }

    @OKFReference {
        docPath = "docs/modules/packet/interleaver.md";
        conceptId = "modules/packet/interleaver";
        section = "REQ-INTERLEAVER-001";
    }
    requirement def <'REQ-INTERLEAVER-001'> REQ_INTERLEAVER_001 {
        doc /* OKF: docs/modules/packet/interleaver.md#REQ-INTERLEAVER-001 */
        require constraint { true == true }
    }

    @OKFReference {
        docPath = "docs/modules/packet/interleaver.md";
        conceptId = "modules/packet/interleaver";
        section = "REQ-INTERLEAVER-002";
    }
    requirement def <'REQ-INTERLEAVER-002'> REQ_INTERLEAVER_002 {
        doc /* OKF: docs/modules/packet/interleaver.md#REQ-INTERLEAVER-002 */
        require constraint { true == true }
    }

    @OKFReference {
        docPath = "docs/modules/packet/interleaver.md";
        conceptId = "modules/packet/interleaver";
        section = "REQ-INTERLEAVER-003";
    }
    requirement def <'REQ-INTERLEAVER-003'> REQ_INTERLEAVER_003 {
        doc /* OKF: docs/modules/packet/interleaver.md#REQ-INTERLEAVER-003 */
        require constraint { true == true }
    }

    @OKFReference {
        docPath = "docs/modules/packet/interleaver.md";
        conceptId = "modules/packet/interleaver";
        section = "REQ-INTERLEAVER-004";
    }
    requirement def <'REQ-INTERLEAVER-004'> REQ_INTERLEAVER_004 {
        doc /* OKF: docs/modules/packet/interleaver.md#REQ-INTERLEAVER-004 */
        require constraint { true == true }
    }

    @OKFReference {
        docPath = "docs/modules/packet/interleaver.md";
        conceptId = "modules/packet/interleaver";
        section = "REQ-INTERLEAVER-005";
    }
    requirement def <'REQ-INTERLEAVER-005'> REQ_INTERLEAVER_005 {
        doc /* OKF: docs/modules/packet/interleaver.md#REQ-INTERLEAVER-005 */
        require constraint { true == true }
    }

    @OKFReference {
        docPath = "docs/modules/packet/packet_join.md";
        conceptId = "modules/packet/packet_join";
        section = "REQ-PACKET_JOIN-001";
    }
    requirement def <'REQ-PACKET_JOIN-001'> REQ_PACKET_JOIN_001 {
        doc /* OKF: docs/modules/packet/packet_join.md#REQ-PACKET_JOIN-001 */
        require constraint { true == true }
    }

    @OKFReference {
        docPath = "docs/modules/packet/packet_join.md";
        conceptId = "modules/packet/packet_join";
        section = "REQ-PACKET_JOIN-002";
    }
    requirement def <'REQ-PACKET_JOIN-002'> REQ_PACKET_JOIN_002 {
        doc /* OKF: docs/modules/packet/packet_join.md#REQ-PACKET_JOIN-002 */
        require constraint { true == true }
    }

    @OKFReference {
        docPath = "docs/modules/packet/packet_join.md";
        conceptId = "modules/packet/packet_join";
        section = "REQ-PACKET_JOIN-003";
    }
    requirement def <'REQ-PACKET_JOIN-003'> REQ_PACKET_JOIN_003 {
        doc /* OKF: docs/modules/packet/packet_join.md#REQ-PACKET_JOIN-003 */
        require constraint { true == true }
    }

    @OKFReference {
        docPath = "docs/modules/packet/packet_join.md";
        conceptId = "modules/packet/packet_join";
        section = "REQ-PACKET_JOIN-004";
    }
    requirement def <'REQ-PACKET_JOIN-004'> REQ_PACKET_JOIN_004 {
        doc /* OKF: docs/modules/packet/packet_join.md#REQ-PACKET_JOIN-004 */
        require constraint { true == true }
    }

    @OKFReference {
        docPath = "docs/modules/packet/packet_join.md";
        conceptId = "modules/packet/packet_join";
        section = "REQ-PACKET_JOIN-005";
    }
    requirement def <'REQ-PACKET_JOIN-005'> REQ_PACKET_JOIN_005 {
        doc /* OKF: docs/modules/packet/packet_join.md#REQ-PACKET_JOIN-005 */
        require constraint { true == true }
    }

    @OKFReference {
        docPath = "docs/modules/packet/packet_join.md";
        conceptId = "modules/packet/packet_join";
        section = "REQ-PACKET_JOIN-006";
    }
    requirement def <'REQ-PACKET_JOIN-006'> REQ_PACKET_JOIN_006 {
        doc /* OKF: docs/modules/packet/packet_join.md#REQ-PACKET_JOIN-006 */
        require constraint { true == true }
    }

    @OKFReference {
        docPath = "docs/modules/packet/packet_join.md";
        conceptId = "modules/packet/packet_join";
        section = "REQ-PACKET_JOIN-007";
    }
    requirement def <'REQ-PACKET_JOIN-007'> REQ_PACKET_JOIN_007 {
        doc /* OKF: docs/modules/packet/packet_join.md#REQ-PACKET_JOIN-007 */
        require constraint { true == true }
    }

    @OKFReference {
        docPath = "docs/modules/packet/packet_delay.md";
        conceptId = "modules/packet/packet_delay";
        section = "REQ-PACKET_DELAY-001";
    }
    requirement def <'REQ-PACKET_DELAY-001'> REQ_PACKET_DELAY_001 {
        doc /* OKF: docs/modules/packet/packet_delay.md#REQ-PACKET_DELAY-001 */
        require constraint { true == true }
    }

    @OKFReference {
        docPath = "docs/modules/packet/packet_delay.md";
        conceptId = "modules/packet/packet_delay";
        section = "REQ-PACKET_DELAY-002";
    }
    requirement def <'REQ-PACKET_DELAY-002'> REQ_PACKET_DELAY_002 {
        doc /* OKF: docs/modules/packet/packet_delay.md#REQ-PACKET_DELAY-002 */
        require constraint { true == true }
    }

    @OKFReference {
        docPath = "docs/modules/packet/packet_delay.md";
        conceptId = "modules/packet/packet_delay";
        section = "REQ-PACKET_DELAY-003";
    }
    requirement def <'REQ-PACKET_DELAY-003'> REQ_PACKET_DELAY_003 {
        doc /* OKF: docs/modules/packet/packet_delay.md#REQ-PACKET_DELAY-003 */
        require constraint { true == true }
    }

    @OKFReference {
        docPath = "docs/modules/packet/packet_delay.md";
        conceptId = "modules/packet/packet_delay";
        section = "REQ-PACKET_DELAY-004";
    }
    requirement def <'REQ-PACKET_DELAY-004'> REQ_PACKET_DELAY_004 {
        doc /* OKF: docs/modules/packet/packet_delay.md#REQ-PACKET_DELAY-004 */
        require constraint { true == true }
    }

    @OKFReference {
        docPath = "docs/modules/packet/packet_delay.md";
        conceptId = "modules/packet/packet_delay";
        section = "REQ-PACKET_DELAY-005";
    }
    requirement def <'REQ-PACKET_DELAY-005'> REQ_PACKET_DELAY_005 {
        doc /* OKF: docs/modules/packet/packet_delay.md#REQ-PACKET_DELAY-005 */
        require constraint { true == true }
    }

    @OKFReference {
        docPath = "docs/modules/packet/packet_delay.md";
        conceptId = "modules/packet/packet_delay";
        section = "REQ-PACKET_DELAY-006";
    }
    requirement def <'REQ-PACKET_DELAY-006'> REQ_PACKET_DELAY_006 {
        doc /* OKF: docs/modules/packet/packet_delay.md#REQ-PACKET_DELAY-006 */
        require constraint { true == true }
    }

    @OKFReference {
        docPath = "docs/modules/misc/be_add_lead.md";
        conceptId = "modules/misc/be_add_lead";
        section = "REQ-BE_ADD_LEAD-001";
    }
    requirement def <'REQ-BE_ADD_LEAD-001'> REQ_BE_ADD_LEAD_001 {
        doc /* OKF: docs/modules/misc/be_add_lead.md#REQ-BE_ADD_LEAD-001 */
        require constraint { true == true }
    }

    @OKFReference {
        docPath = "docs/modules/misc/be_add_lead.md";
        conceptId = "modules/misc/be_add_lead";
        section = "REQ-BE_ADD_LEAD-002";
    }
    requirement def <'REQ-BE_ADD_LEAD-002'> REQ_BE_ADD_LEAD_002 {
        doc /* OKF: docs/modules/misc/be_add_lead.md#REQ-BE_ADD_LEAD-002 */
        require constraint { true == true }
    }

    @OKFReference {
        docPath = "docs/modules/misc/be_add_lead.md";
        conceptId = "modules/misc/be_add_lead";
        section = "REQ-BE_ADD_LEAD-003";
    }
    requirement def <'REQ-BE_ADD_LEAD-003'> REQ_BE_ADD_LEAD_003 {
        doc /* OKF: docs/modules/misc/be_add_lead.md#REQ-BE_ADD_LEAD-003 */
        require constraint { true == true }
    }

    @OKFReference {
        docPath = "docs/modules/misc/be_add_trail.md";
        conceptId = "modules/misc/be_add_trail";
        section = "REQ-BE_ADD_TRAIL-001";
    }
    requirement def <'REQ-BE_ADD_TRAIL-001'> REQ_BE_ADD_TRAIL_001 {
        doc /* OKF: docs/modules/misc/be_add_trail.md#REQ-BE_ADD_TRAIL-001 */
        require constraint { true == true }
    }

    @OKFReference {
        docPath = "docs/modules/misc/be_add_trail.md";
        conceptId = "modules/misc/be_add_trail";
        section = "REQ-BE_ADD_TRAIL-002";
    }
    requirement def <'REQ-BE_ADD_TRAIL-002'> REQ_BE_ADD_TRAIL_002 {
        doc /* OKF: docs/modules/misc/be_add_trail.md#REQ-BE_ADD_TRAIL-002 */
        require constraint { true == true }
    }

    @OKFReference {
        docPath = "docs/modules/misc/be_add_trail.md";
        conceptId = "modules/misc/be_add_trail";
        section = "REQ-BE_ADD_TRAIL-003";
    }
    requirement def <'REQ-BE_ADD_TRAIL-003'> REQ_BE_ADD_TRAIL_003 {
        doc /* OKF: docs/modules/misc/be_add_trail.md#REQ-BE_ADD_TRAIL-003 */
        require constraint { true == true }
    }

    @OKFReference {
        docPath = "docs/modules/misc/be_remove_lead.md";
        conceptId = "modules/misc/be_remove_lead";
        section = "REQ-BE_REMOVE_LEAD-001";
    }
    requirement def <'REQ-BE_REMOVE_LEAD-001'> REQ_BE_REMOVE_LEAD_001 {
        doc /* OKF: docs/modules/misc/be_remove_lead.md#REQ-BE_REMOVE_LEAD-001 */
        require constraint { true == true }
    }

    @OKFReference {
        docPath = "docs/modules/misc/be_remove_lead.md";
        conceptId = "modules/misc/be_remove_lead";
        section = "REQ-BE_REMOVE_LEAD-002";
    }
    requirement def <'REQ-BE_REMOVE_LEAD-002'> REQ_BE_REMOVE_LEAD_002 {
        doc /* OKF: docs/modules/misc/be_remove_lead.md#REQ-BE_REMOVE_LEAD-002 */
        require constraint { true == true }
    }

    @OKFReference {
        docPath = "docs/modules/misc/be_remove_lead.md";
        conceptId = "modules/misc/be_remove_lead";
        section = "REQ-BE_REMOVE_LEAD-003";
    }
    requirement def <'REQ-BE_REMOVE_LEAD-003'> REQ_BE_REMOVE_LEAD_003 {
        doc /* OKF: docs/modules/misc/be_remove_lead.md#REQ-BE_REMOVE_LEAD-003 */
        require constraint { true == true }
    }

    @OKFReference {
        docPath = "docs/modules/misc/be_remove_trail.md";
        conceptId = "modules/misc/be_remove_trail";
        section = "REQ-BE_REMOVE_TRAIL-001";
    }
    requirement def <'REQ-BE_REMOVE_TRAIL-001'> REQ_BE_REMOVE_TRAIL_001 {
        doc /* OKF: docs/modules/misc/be_remove_trail.md#REQ-BE_REMOVE_TRAIL-001 */
        require constraint { true == true }
    }

    @OKFReference {
        docPath = "docs/modules/misc/be_remove_trail.md";
        conceptId = "modules/misc/be_remove_trail";
        section = "REQ-BE_REMOVE_TRAIL-002";
    }
    requirement def <'REQ-BE_REMOVE_TRAIL-002'> REQ_BE_REMOVE_TRAIL_002 {
        doc /* OKF: docs/modules/misc/be_remove_trail.md#REQ-BE_REMOVE_TRAIL-002 */
        require constraint { true == true }
    }

    @OKFReference {
        docPath = "docs/modules/misc/be_remove_trail.md";
        conceptId = "modules/misc/be_remove_trail";
        section = "REQ-BE_REMOVE_TRAIL-003";
    }
    requirement def <'REQ-BE_REMOVE_TRAIL-003'> REQ_BE_REMOVE_TRAIL_003 {
        doc /* OKF: docs/modules/misc/be_remove_trail.md#REQ-BE_REMOVE_TRAIL-003 */
        require constraint { true == true }
    }

    @OKFReference {
        docPath = "docs/modules/comms/gearbox.md";
        conceptId = "modules/comms/gearbox";
        section = "REQ-GEARBOX-001";
    }
    requirement def <'REQ-GEARBOX-001'> REQ_GEARBOX_001 {
        doc /* OKF: docs/modules/comms/gearbox.md#REQ-GEARBOX-001 */
        require constraint { true == true }
    }

    @OKFReference {
        docPath = "docs/modules/comms/gearbox.md";
        conceptId = "modules/comms/gearbox";
        section = "REQ-GEARBOX-002";
    }
    requirement def <'REQ-GEARBOX-002'> REQ_GEARBOX_002 {
        doc /* OKF: docs/modules/comms/gearbox.md#REQ-GEARBOX-002 */
        require constraint { true == true }
    }

    @OKFReference {
        docPath = "docs/modules/comms/gearbox.md";
        conceptId = "modules/comms/gearbox";
        section = "REQ-GEARBOX-003";
    }
    requirement def <'REQ-GEARBOX-003'> REQ_GEARBOX_003 {
        doc /* OKF: docs/modules/comms/gearbox.md#REQ-GEARBOX-003 */
        require constraint { true == true }
    }

    @OKFReference {
        docPath = "docs/modules/comms/gearbox.md";
        conceptId = "modules/comms/gearbox";
        section = "REQ-GEARBOX-004";
    }
    requirement def <'REQ-GEARBOX-004'> REQ_GEARBOX_004 {
        doc /* OKF: docs/modules/comms/gearbox.md#REQ-GEARBOX-004 */
        require constraint { true == true }
    }

    @OKFReference {
        docPath = "docs/modules/comms/gearbox.md";
        conceptId = "modules/comms/gearbox";
        section = "REQ-GEARBOX-005";
    }
    requirement def <'REQ-GEARBOX-005'> REQ_GEARBOX_005 {
        doc /* OKF: docs/modules/comms/gearbox.md#REQ-GEARBOX-005 */
        require constraint { true == true }
    }

    @OKFReference {
        docPath = "docs/modules/comms/gearbox.md";
        conceptId = "modules/comms/gearbox";
        section = "REQ-GEARBOX-006";
    }
    requirement def <'REQ-GEARBOX-006'> REQ_GEARBOX_006 {
        doc /* OKF: docs/modules/comms/gearbox.md#REQ-GEARBOX-006 */
        require constraint { true == true }
    }

    @OKFReference {
        docPath = "docs/modules/endec/rle_encode.md";
        conceptId = "modules/endec/rle_encode";
        section = "REQ-RLE_ENCODE-001";
    }
    requirement def <'REQ-RLE_ENCODE-001'> REQ_RLE_ENCODE_001 {
        doc /* OKF: docs/modules/endec/rle_encode.md#REQ-RLE_ENCODE-001 */
        require constraint { true == true }
    }

    @OKFReference {
        docPath = "docs/modules/endec/rle_encode.md";
        conceptId = "modules/endec/rle_encode";
        section = "REQ-RLE_ENCODE-002";
    }
    requirement def <'REQ-RLE_ENCODE-002'> REQ_RLE_ENCODE_002 {
        doc /* OKF: docs/modules/endec/rle_encode.md#REQ-RLE_ENCODE-002 */
        require constraint { true == true }
    }

    @OKFReference {
        docPath = "docs/modules/endec/rle_encode.md";
        conceptId = "modules/endec/rle_encode";
        section = "REQ-RLE_ENCODE-003";
    }
    requirement def <'REQ-RLE_ENCODE-003'> REQ_RLE_ENCODE_003 {
        doc /* OKF: docs/modules/endec/rle_encode.md#REQ-RLE_ENCODE-003 */
        require constraint { true == true }
    }

    @OKFReference {
        docPath = "docs/modules/endec/rle_encode.md";
        conceptId = "modules/endec/rle_encode";
        section = "REQ-RLE_ENCODE-004";
    }
    requirement def <'REQ-RLE_ENCODE-004'> REQ_RLE_ENCODE_004 {
        doc /* OKF: docs/modules/endec/rle_encode.md#REQ-RLE_ENCODE-004 */
        require constraint { true == true }
    }

    @OKFReference {
        docPath = "docs/modules/endec/rle_encode.md";
        conceptId = "modules/endec/rle_encode";
        section = "REQ-RLE_ENCODE-005";
    }
    requirement def <'REQ-RLE_ENCODE-005'> REQ_RLE_ENCODE_005 {
        doc /* OKF: docs/modules/endec/rle_encode.md#REQ-RLE_ENCODE-005 */
        require constraint { true == true }
    }

    @OKFReference {
        docPath = "docs/modules/endec/rle_encode.md";
        conceptId = "modules/endec/rle_encode";
        section = "REQ-RLE_ENCODE-006";
    }
    requirement def <'REQ-RLE_ENCODE-006'> REQ_RLE_ENCODE_006 {
        doc /* OKF: docs/modules/endec/rle_encode.md#REQ-RLE_ENCODE-006 */
        require constraint { true == true }
    }

    @OKFReference {
        docPath = "docs/modules/endec/rle_encode.md";
        conceptId = "modules/endec/rle_encode";
        section = "REQ-RLE_ENCODE-007";
    }
    requirement def <'REQ-RLE_ENCODE-007'> REQ_RLE_ENCODE_007 {
        doc /* OKF: docs/modules/endec/rle_encode.md#REQ-RLE_ENCODE-007 */
        require constraint { true == true }
    }

    @OKFReference {
        docPath = "docs/modules/endec/rle_encode.md";
        conceptId = "modules/endec/rle_encode";
        section = "REQ-RLE_ENCODE-008";
    }
    requirement def <'REQ-RLE_ENCODE-008'> REQ_RLE_ENCODE_008 {
        doc /* OKF: docs/modules/endec/rle_encode.md#REQ-RLE_ENCODE-008 */
        require constraint { true == true }
    }

    @OKFReference {
        docPath = "docs/modules/endec/rle_decode.md";
        conceptId = "modules/endec/rle_decode";
        section = "REQ-RLE_DECODE-001";
    }
    requirement def <'REQ-RLE_DECODE-001'> REQ_RLE_DECODE_001 {
        doc /* OKF: docs/modules/endec/rle_decode.md#REQ-RLE_DECODE-001 */
        require constraint { true == true }
    }

    @OKFReference {
        docPath = "docs/modules/endec/rle_decode.md";
        conceptId = "modules/endec/rle_decode";
        section = "REQ-RLE_DECODE-002";
    }
    requirement def <'REQ-RLE_DECODE-002'> REQ_RLE_DECODE_002 {
        doc /* OKF: docs/modules/endec/rle_decode.md#REQ-RLE_DECODE-002 */
        require constraint { true == true }
    }

    @OKFReference {
        docPath = "docs/modules/endec/rle_decode.md";
        conceptId = "modules/endec/rle_decode";
        section = "REQ-RLE_DECODE-003";
    }
    requirement def <'REQ-RLE_DECODE-003'> REQ_RLE_DECODE_003 {
        doc /* OKF: docs/modules/endec/rle_decode.md#REQ-RLE_DECODE-003 */
        require constraint { true == true }
    }

    @OKFReference {
        docPath = "docs/modules/endec/rle_decode.md";
        conceptId = "modules/endec/rle_decode";
        section = "REQ-RLE_DECODE-004";
    }
    requirement def <'REQ-RLE_DECODE-004'> REQ_RLE_DECODE_004 {
        doc /* OKF: docs/modules/endec/rle_decode.md#REQ-RLE_DECODE-004 */
        require constraint { true == true }
    }

    @OKFReference {
        docPath = "docs/modules/interfaces/axis_to_avst.md";
        conceptId = "modules/interfaces/axis_to_avst";
        section = "REQ-AXIS_TO_AVST-001";
    }
    requirement def <'REQ-AXIS_TO_AVST-001'> REQ_AXIS_TO_AVST_001 {
        doc /* OKF: docs/modules/interfaces/axis_to_avst.md#REQ-AXIS_TO_AVST-001 */
        require constraint { true == true }
    }

    @OKFReference {
        docPath = "docs/modules/interfaces/axis_to_avst.md";
        conceptId = "modules/interfaces/axis_to_avst";
        section = "REQ-AXIS_TO_AVST-002";
    }
    requirement def <'REQ-AXIS_TO_AVST-002'> REQ_AXIS_TO_AVST_002 {
        doc /* OKF: docs/modules/interfaces/axis_to_avst.md#REQ-AXIS_TO_AVST-002 */
        require constraint { true == true }
    }

    @OKFReference {
        docPath = "docs/modules/interfaces/axis_to_avst.md";
        conceptId = "modules/interfaces/axis_to_avst";
        section = "REQ-AXIS_TO_AVST-003";
    }
    requirement def <'REQ-AXIS_TO_AVST-003'> REQ_AXIS_TO_AVST_003 {
        doc /* OKF: docs/modules/interfaces/axis_to_avst.md#REQ-AXIS_TO_AVST-003 */
        require constraint { true == true }
    }

    @OKFReference {
        docPath = "docs/modules/interfaces/axis_to_avst.md";
        conceptId = "modules/interfaces/axis_to_avst";
        section = "REQ-AXIS_TO_AVST-004";
    }
    requirement def <'REQ-AXIS_TO_AVST-004'> REQ_AXIS_TO_AVST_004 {
        doc /* OKF: docs/modules/interfaces/axis_to_avst.md#REQ-AXIS_TO_AVST-004 */
        require constraint { true == true }
    }

    @OKFReference {
        docPath = "docs/modules/interfaces/avst_to_axis.md";
        conceptId = "modules/interfaces/avst_to_axis";
        section = "REQ-AVST_TO_AXIS-001";
    }
    requirement def <'REQ-AVST_TO_AXIS-001'> REQ_AVST_TO_AXIS_001 {
        doc /* OKF: docs/modules/interfaces/avst_to_axis.md#REQ-AVST_TO_AXIS-001 */
        require constraint { true == true }
    }

    @OKFReference {
        docPath = "docs/modules/interfaces/avst_to_axis.md";
        conceptId = "modules/interfaces/avst_to_axis";
        section = "REQ-AVST_TO_AXIS-002";
    }
    requirement def <'REQ-AVST_TO_AXIS-002'> REQ_AVST_TO_AXIS_002 {
        doc /* OKF: docs/modules/interfaces/avst_to_axis.md#REQ-AVST_TO_AXIS-002 */
        require constraint { true == true }
    }

    @OKFReference {
        docPath = "docs/modules/interfaces/avst_ram_write.md";
        conceptId = "modules/interfaces/avst_ram_write";
        section = "REQ-AVST_RAM_WRITE-001";
    }
    requirement def <'REQ-AVST_RAM_WRITE-001'> REQ_AVST_RAM_WRITE_001 {
        doc /* OKF: docs/modules/interfaces/avst_ram_write.md#REQ-AVST_RAM_WRITE-001 */
        require constraint { true == true }
    }

    @OKFReference {
        docPath = "docs/modules/interfaces/avst_ram_write.md";
        conceptId = "modules/interfaces/avst_ram_write";
        section = "REQ-AVST_RAM_WRITE-002";
    }
    requirement def <'REQ-AVST_RAM_WRITE-002'> REQ_AVST_RAM_WRITE_002 {
        doc /* OKF: docs/modules/interfaces/avst_ram_write.md#REQ-AVST_RAM_WRITE-002 */
        require constraint { true == true }
    }

    @OKFReference {
        docPath = "docs/modules/interfaces/avst_ram_write.md";
        conceptId = "modules/interfaces/avst_ram_write";
        section = "REQ-AVST_RAM_WRITE-003";
    }
    requirement def <'REQ-AVST_RAM_WRITE-003'> REQ_AVST_RAM_WRITE_003 {
        doc /* OKF: docs/modules/interfaces/avst_ram_write.md#REQ-AVST_RAM_WRITE-003 */
        require constraint { true == true }
    }

    @OKFReference {
        docPath = "docs/modules/interfaces/avst_ram_write.md";
        conceptId = "modules/interfaces/avst_ram_write";
        section = "REQ-AVST_RAM_WRITE-004";
    }
    requirement def <'REQ-AVST_RAM_WRITE-004'> REQ_AVST_RAM_WRITE_004 {
        doc /* OKF: docs/modules/interfaces/avst_ram_write.md#REQ-AVST_RAM_WRITE-004 */
        require constraint { true == true }
    }

    @OKFReference {
        docPath = "docs/modules/interfaces/avst_ram_write.md";
        conceptId = "modules/interfaces/avst_ram_write";
        section = "REQ-AVST_RAM_WRITE-005";
    }
    requirement def <'REQ-AVST_RAM_WRITE-005'> REQ_AVST_RAM_WRITE_005 {
        doc /* OKF: docs/modules/interfaces/avst_ram_write.md#REQ-AVST_RAM_WRITE-005 */
        require constraint { true == true }
    }

    @OKFReference {
        docPath = "docs/modules/interfaces/avst_ram_write_unaligned.md";
        conceptId = "modules/interfaces/avst_ram_write_unaligned";
        section = "REQ-AVST_RAM_WRITE_UNALIGNED-001";
    }
    requirement def <'REQ-AVST_RAM_WRITE_UNALIGNED-001'> REQ_AVST_RAM_WRITE_UNALIGNED_001 {
        doc /* OKF: docs/modules/interfaces/avst_ram_write_unaligned.md#REQ-AVST_RAM_WRITE_UNALIGNED-001 */
        require constraint { true == true }
    }

    @OKFReference {
        docPath = "docs/modules/interfaces/avst_ram_write_unaligned.md";
        conceptId = "modules/interfaces/avst_ram_write_unaligned";
        section = "REQ-AVST_RAM_WRITE_UNALIGNED-002";
    }
    requirement def <'REQ-AVST_RAM_WRITE_UNALIGNED-002'> REQ_AVST_RAM_WRITE_UNALIGNED_002 {
        doc /* OKF: docs/modules/interfaces/avst_ram_write_unaligned.md#REQ-AVST_RAM_WRITE_UNALIGNED-002 */
        require constraint { true == true }
    }

    @OKFReference {
        docPath = "docs/modules/interfaces/avst_ram_write_unaligned.md";
        conceptId = "modules/interfaces/avst_ram_write_unaligned";
        section = "REQ-AVST_RAM_WRITE_UNALIGNED-003";
    }
    requirement def <'REQ-AVST_RAM_WRITE_UNALIGNED-003'> REQ_AVST_RAM_WRITE_UNALIGNED_003 {
        doc /* OKF: docs/modules/interfaces/avst_ram_write_unaligned.md#REQ-AVST_RAM_WRITE_UNALIGNED-003 */
        require constraint { true == true }
    }

    @OKFReference {
        docPath = "docs/modules/interfaces/avst_ram_write_unaligned.md";
        conceptId = "modules/interfaces/avst_ram_write_unaligned";
        section = "REQ-AVST_RAM_WRITE_UNALIGNED-004";
    }
    requirement def <'REQ-AVST_RAM_WRITE_UNALIGNED-004'> REQ_AVST_RAM_WRITE_UNALIGNED_004 {
        doc /* OKF: docs/modules/interfaces/avst_ram_write_unaligned.md#REQ-AVST_RAM_WRITE_UNALIGNED-004 */
        require constraint { true == true }
    }

    @OKFReference {
        docPath = "docs/modules/interfaces/avst_ram_write_unaligned.md";
        conceptId = "modules/interfaces/avst_ram_write_unaligned";
        section = "REQ-AVST_RAM_WRITE_UNALIGNED-005";
    }
    requirement def <'REQ-AVST_RAM_WRITE_UNALIGNED-005'> REQ_AVST_RAM_WRITE_UNALIGNED_005 {
        doc /* OKF: docs/modules/interfaces/avst_ram_write_unaligned.md#REQ-AVST_RAM_WRITE_UNALIGNED-005 */
        require constraint { true == true }
    }

    @OKFReference {
        docPath = "docs/modules/interfaces/avst_ram_write_unaligned.md";
        conceptId = "modules/interfaces/avst_ram_write_unaligned";
        section = "REQ-AVST_RAM_WRITE_UNALIGNED-006";
    }
    requirement def <'REQ-AVST_RAM_WRITE_UNALIGNED-006'> REQ_AVST_RAM_WRITE_UNALIGNED_006 {
        doc /* OKF: docs/modules/interfaces/avst_ram_write_unaligned.md#REQ-AVST_RAM_WRITE_UNALIGNED-006 */
        require constraint { true == true }
    }

    @OKFReference {
        docPath = "docs/modules/interfaces/avst_ram_write_unaligned.md";
        conceptId = "modules/interfaces/avst_ram_write_unaligned";
        section = "REQ-AVST_RAM_WRITE_UNALIGNED-007";
    }
    requirement def <'REQ-AVST_RAM_WRITE_UNALIGNED-007'> REQ_AVST_RAM_WRITE_UNALIGNED_007 {
        doc /* OKF: docs/modules/interfaces/avst_ram_write_unaligned.md#REQ-AVST_RAM_WRITE_UNALIGNED-007 */
        require constraint { true == true }
    }

    @OKFReference {
        docPath = "docs/modules/interfaces/avst_ram_write_unaligned.md";
        conceptId = "modules/interfaces/avst_ram_write_unaligned";
        section = "REQ-AVST_RAM_WRITE_UNALIGNED-008";
    }
    requirement def <'REQ-AVST_RAM_WRITE_UNALIGNED-008'> REQ_AVST_RAM_WRITE_UNALIGNED_008 {
        doc /* OKF: docs/modules/interfaces/avst_ram_write_unaligned.md#REQ-AVST_RAM_WRITE_UNALIGNED-008 */
        require constraint { true == true }
    }

    @OKFReference {
        docPath = "docs/modules/interfaces/avst_ram_write_unaligned.md";
        conceptId = "modules/interfaces/avst_ram_write_unaligned";
        section = "REQ-AVST_RAM_WRITE_UNALIGNED-009";
    }
    requirement def <'REQ-AVST_RAM_WRITE_UNALIGNED-009'> REQ_AVST_RAM_WRITE_UNALIGNED_009 {
        doc /* OKF: docs/modules/interfaces/avst_ram_write_unaligned.md#REQ-AVST_RAM_WRITE_UNALIGNED-009 */
        require constraint { true == true }
    }

    @OKFReference {
        docPath = "docs/modules/interfaces/avst_ram_write_unaligned.md";
        conceptId = "modules/interfaces/avst_ram_write_unaligned";
        section = "REQ-AVST_RAM_WRITE_UNALIGNED-010";
    }
    requirement def <'REQ-AVST_RAM_WRITE_UNALIGNED-010'> REQ_AVST_RAM_WRITE_UNALIGNED_010 {
        doc /* OKF: docs/modules/interfaces/avst_ram_write_unaligned.md#REQ-AVST_RAM_WRITE_UNALIGNED-010 */
        require constraint { true == true }
    }

    @OKFReference {
        docPath = "docs/modules/interfaces/avst_ram_write_unaligned.md";
        conceptId = "modules/interfaces/avst_ram_write_unaligned";
        section = "REQ-AVST_RAM_WRITE_UNALIGNED-011";
    }
    requirement def <'REQ-AVST_RAM_WRITE_UNALIGNED-011'> REQ_AVST_RAM_WRITE_UNALIGNED_011 {
        doc /* OKF: docs/modules/interfaces/avst_ram_write_unaligned.md#REQ-AVST_RAM_WRITE_UNALIGNED-011 */
        require constraint { true == true }
    }

    @OKFReference {
        docPath = "docs/modules/interfaces/avst_ram_write_unaligned.md";
        conceptId = "modules/interfaces/avst_ram_write_unaligned";
        section = "REQ-AVST_RAM_WRITE_UNALIGNED-012";
    }
    requirement def <'REQ-AVST_RAM_WRITE_UNALIGNED-012'> REQ_AVST_RAM_WRITE_UNALIGNED_012 {
        doc /* OKF: docs/modules/interfaces/avst_ram_write_unaligned.md#REQ-AVST_RAM_WRITE_UNALIGNED-012 */
        require constraint { true == true }
    }

    @OKFReference {
        docPath = "docs/modules/interfaces/avst_ram_write_unaligned.md";
        conceptId = "modules/interfaces/avst_ram_write_unaligned";
        section = "REQ-AVST_RAM_WRITE_UNALIGNED-013";
    }
    requirement def <'REQ-AVST_RAM_WRITE_UNALIGNED-013'> REQ_AVST_RAM_WRITE_UNALIGNED_013 {
        doc /* OKF: docs/modules/interfaces/avst_ram_write_unaligned.md#REQ-AVST_RAM_WRITE_UNALIGNED-013 */
        require constraint { true == true }
    }

    @OKFReference {
        docPath = "docs/modules/interfaces/avst_ram_write_unaligned.md";
        conceptId = "modules/interfaces/avst_ram_write_unaligned";
        section = "REQ-AVST_RAM_WRITE_UNALIGNED-014";
    }
    requirement def <'REQ-AVST_RAM_WRITE_UNALIGNED-014'> REQ_AVST_RAM_WRITE_UNALIGNED_014 {
        doc /* OKF: docs/modules/interfaces/avst_ram_write_unaligned.md#REQ-AVST_RAM_WRITE_UNALIGNED-014 */
        require constraint { true == true }
    }

    @OKFReference {
        docPath = "docs/modules/interfaces/avst_ram_write_unaligned.md";
        conceptId = "modules/interfaces/avst_ram_write_unaligned";
        section = "REQ-AVST_RAM_WRITE_UNALIGNED-015";
    }
    requirement def <'REQ-AVST_RAM_WRITE_UNALIGNED-015'> REQ_AVST_RAM_WRITE_UNALIGNED_015 {
        doc /* OKF: docs/modules/interfaces/avst_ram_write_unaligned.md#REQ-AVST_RAM_WRITE_UNALIGNED-015 */
        require constraint { true == true }
    }

    @OKFReference {
        docPath = "docs/modules/interfaces/avst_ram_read.md";
        conceptId = "modules/interfaces/avst_ram_read";
        section = "REQ-AVST_RAM_READ-001";
    }
    requirement def <'REQ-AVST_RAM_READ-001'> REQ_AVST_RAM_READ_001 {
        doc /* OKF: docs/modules/interfaces/avst_ram_read.md#REQ-AVST_RAM_READ-001 */
        require constraint { true == true }
    }

    @OKFReference {
        docPath = "docs/modules/interfaces/avst_ram_read.md";
        conceptId = "modules/interfaces/avst_ram_read";
        section = "REQ-AVST_RAM_READ-002";
    }
    requirement def <'REQ-AVST_RAM_READ-002'> REQ_AVST_RAM_READ_002 {
        doc /* OKF: docs/modules/interfaces/avst_ram_read.md#REQ-AVST_RAM_READ-002 */
        require constraint { true == true }
    }

    @OKFReference {
        docPath = "docs/modules/interfaces/avst_ram_read.md";
        conceptId = "modules/interfaces/avst_ram_read";
        section = "REQ-AVST_RAM_READ-003";
    }
    requirement def <'REQ-AVST_RAM_READ-003'> REQ_AVST_RAM_READ_003 {
        doc /* OKF: docs/modules/interfaces/avst_ram_read.md#REQ-AVST_RAM_READ-003 */
        require constraint { true == true }
    }

    @OKFReference {
        docPath = "docs/modules/interfaces/avst_ram_read.md";
        conceptId = "modules/interfaces/avst_ram_read";
        section = "REQ-AVST_RAM_READ-004";
    }
    requirement def <'REQ-AVST_RAM_READ-004'> REQ_AVST_RAM_READ_004 {
        doc /* OKF: docs/modules/interfaces/avst_ram_read.md#REQ-AVST_RAM_READ-004 */
        require constraint { true == true }
    }

    @OKFReference {
        docPath = "docs/modules/interfaces/avst_ram_read.md";
        conceptId = "modules/interfaces/avst_ram_read";
        section = "REQ-AVST_RAM_READ-005";
    }
    requirement def <'REQ-AVST_RAM_READ-005'> REQ_AVST_RAM_READ_005 {
        doc /* OKF: docs/modules/interfaces/avst_ram_read.md#REQ-AVST_RAM_READ-005 */
        require constraint { true == true }
    }

    @OKFReference {
        docPath = "docs/modules/interfaces/avst_ram_read.md";
        conceptId = "modules/interfaces/avst_ram_read";
        section = "REQ-AVST_RAM_READ-006";
    }
    requirement def <'REQ-AVST_RAM_READ-006'> REQ_AVST_RAM_READ_006 {
        doc /* OKF: docs/modules/interfaces/avst_ram_read.md#REQ-AVST_RAM_READ-006 */
        require constraint { true == true }
    }

    @OKFReference {
        docPath = "docs/modules/interfaces/avst_ram_read.md";
        conceptId = "modules/interfaces/avst_ram_read";
        section = "REQ-AVST_RAM_READ-007";
    }
    requirement def <'REQ-AVST_RAM_READ-007'> REQ_AVST_RAM_READ_007 {
        doc /* OKF: docs/modules/interfaces/avst_ram_read.md#REQ-AVST_RAM_READ-007 */
        require constraint { true == true }
    }

    @OKFReference {
        docPath = "docs/modules/interfaces/avst_ram_read.md";
        conceptId = "modules/interfaces/avst_ram_read";
        section = "REQ-AVST_RAM_READ-008";
    }
    requirement def <'REQ-AVST_RAM_READ-008'> REQ_AVST_RAM_READ_008 {
        doc /* OKF: docs/modules/interfaces/avst_ram_read.md#REQ-AVST_RAM_READ-008 */
        require constraint { true == true }
    }

    @OKFReference {
        docPath = "docs/modules/interfaces/avst_ram_read.md";
        conceptId = "modules/interfaces/avst_ram_read";
        section = "REQ-AVST_RAM_READ-009";
    }
    requirement def <'REQ-AVST_RAM_READ-009'> REQ_AVST_RAM_READ_009 {
        doc /* OKF: docs/modules/interfaces/avst_ram_read.md#REQ-AVST_RAM_READ-009 */
        require constraint { true == true }
    }

    @OKFReference {
        docPath = "docs/modules/interfaces/avst_ram_read.md";
        conceptId = "modules/interfaces/avst_ram_read";
        section = "REQ-AVST_RAM_READ-010";
    }
    requirement def <'REQ-AVST_RAM_READ-010'> REQ_AVST_RAM_READ_010 {
        doc /* OKF: docs/modules/interfaces/avst_ram_read.md#REQ-AVST_RAM_READ-010 */
        require constraint { true == true }
    }

    @OKFReference {
        docPath = "docs/modules/interfaces/avst_ram_read.md";
        conceptId = "modules/interfaces/avst_ram_read";
        section = "REQ-AVST_RAM_READ-011";
    }
    requirement def <'REQ-AVST_RAM_READ-011'> REQ_AVST_RAM_READ_011 {
        doc /* OKF: docs/modules/interfaces/avst_ram_read.md#REQ-AVST_RAM_READ-011 */
        require constraint { true == true }
    }

    @OKFReference {
        docPath = "docs/modules/interfaces/avst_ram_read.md";
        conceptId = "modules/interfaces/avst_ram_read";
        section = "REQ-AVST_RAM_READ-012";
    }
    requirement def <'REQ-AVST_RAM_READ-012'> REQ_AVST_RAM_READ_012 {
        doc /* OKF: docs/modules/interfaces/avst_ram_read.md#REQ-AVST_RAM_READ-012 */
        require constraint { true == true }
    }

    @OKFReference {
        docPath = "docs/modules/interfaces/avst_ram_read.md";
        conceptId = "modules/interfaces/avst_ram_read";
        section = "REQ-AVST_RAM_READ-013";
    }
    requirement def <'REQ-AVST_RAM_READ-013'> REQ_AVST_RAM_READ_013 {
        doc /* OKF: docs/modules/interfaces/avst_ram_read.md#REQ-AVST_RAM_READ-013 */
        require constraint { true == true }
    }
}
